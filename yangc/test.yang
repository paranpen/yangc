// Contents of "lte-nodeb-system.yang"
module nodeb-system {
  namespace "lte";
  prefix "lte";
  description "test yang module";
  
  typedef board-type {
    description "Type definition: board-type";
    type enumeration {
        enum umc{
          value 7;
        }
        enum upc {
          value 9;
          description "enum UPC";
        }
    }
  }

  typedef my-type {
    description "Type definition: my-type int32";
    type int32;
  }

  list table {
    description "List definition: table";
    key board-id;
    leaf board-id {
      type enumeration {
          enum BOARD_ID1 {
            value 1;
            description "enum BOARD_ID1";
          }
      }
      description "what is board-id?";
    }
    leaf board1 {
      type board-type;
      description "BOARD1";
    }

    leaf board2 {
      type board-type;
      description "BOARD2";
    }
    
    leaf board-name {
      type my-type;
      description "NAME...";
    }
  }
}
